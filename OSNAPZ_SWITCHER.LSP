(defun C:q()
(setq lastosnapz (getvar "OSNAPZ"))
(if (= lastosnapz 0)
	(setvar "OSNAPZ" 1)
	(setvar "OSNAPZ" 0)
)
(setq newosnapz (getvar "OSNAPZ"))
(princ "\nNowe ustawienie OSNAPZ: ")
(princ newosnapz)
(princ)
)
